module rest {
    yang-version 1.1;
    namespace "urn:opendaylight:params:xml:ns:yang:rest";
    prefix "rest";

    revision "2017-08-30" { // TODO change revision to date of model creation
        description "Initial revision of rest model";
    }
     rpc hello {
            description "";
            input {
                leaf in {
                    description "";
                    type string;
                }
            }

            output {
                leaf out {
                    description "";
                    type string;
                }
            }
        }
}
